(defun C:OVERKILLCLEAN (/ original-layout)
  (setq original-layout (getvar "ctab"))

  (princ "\n==================================================")
  (princ "\nЗадача 4: Удаление дублирующихся объектов")
  (princ "\n==================================================")

  ; Отключаем эхо команд
  (setvar "cmdecho" 0)

  ; Переходим на лист Model
  (princ "\n📄 Переход на лист Model...")
  (setvar "ctab" "Model")
  (princ " ✅")

  ; Запускаем OVERKILL через командную строку (.- префикс подавляет диалог)
  (princ "\n🧹 Запуск OVERKILL...")

  ; Выбираем все объекты и запускаем OVERKILL с параметрами по умолчанию
  (command "_.-OVERKILL" "_ALL" "" "")

  (princ " ✅")

  ; Возвращаемся на исходный лист
  (princ (strcat "\n📄 Возврат на исходный лист: " original-layout))
  (setvar "ctab" original-layout)
  (princ " ✅")

  ; Включаем обратно эхо команд
  (setvar "cmdecho" 1)

  (princ "\n\n==================================================")
  (princ "\n✅ OVERKILL завершен!")
  (princ "\n==================================================")
  (princ "\n\n💡 Для просмотра подробной статистики:")
  (princ "\n   нажмите F2 в AutoCAD и посмотрите")
  (princ "\n   сколько объектов было удалено.")
  (princ "\n==================================================")
  (princ)
)
