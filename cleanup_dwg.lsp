(defun C:CLEANUP (/ original-layout)
  (setq original-layout (getvar "ctab"))

  (princ "\n==================================================")
  (princ "\nЗадача 3: Очистка чертежа")
  (princ "\n==================================================")

  ; Отключаем эхо команд
  (setvar "cmdecho" 0)

  ; Переходим на лист Model
  (princ "\n📄 Переход на лист Model...")
  (setvar "ctab" "Model")
  (princ " ✅")

  ; Очистка с отображением статистики
  (princ "\n🧹 Очистка неиспользуемых элементов...")
  (princ "\n")

  ; Повторяем очистку 3 раза
  (repeat 3
    (command "_.-PURGE" "_A" "*" "_N")
  )

  (princ "\n  ✅ Очистка выполнена")

  ; Возвращаемся на исходный лист
  (princ (strcat "\n📄 Возврат на исходный лист: " original-layout))
  (setvar "ctab" original-layout)
  (princ " ✅")

  ; Включаем обратно эхо команд
  (setvar "cmdecho" 1)

  (princ "\n\n==================================================")
  (princ "\n✅ Очистка завершена!")
  (princ "\n==================================================")
  (princ "\n\n💡 Для просмотра подробной статистики:")
  (princ "\n   нажмите F2 в AutoCAD и посмотрите")
  (princ "\n   какие элементы были удалены.")
  (princ "\n==================================================")
  (princ)
)
