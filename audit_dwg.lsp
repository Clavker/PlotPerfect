(defun C:AUDITDWG (/ original-layout)
  (setq original-layout (getvar "ctab"))

  (princ "\n==================================================")
  (princ "\nЗадача 5: Проверка и исправление ошибок чертежа")
  (princ "\n==================================================")

  ; Отключаем эхо команд
  (setvar "cmdecho" 0)

  ; Переходим на лист Model
  (princ "\n📄 Переход на лист Model...")
  (setvar "ctab" "Model")
  (princ " ✅")

  ; Запускаем AUDIT с автоматическим исправлением (Y - Yes)
  (princ "\n🔍 Запуск проверки чертежа (AUDIT)...")
  (command "_.AUDIT" "_Y")

  (princ " ✅")

  ; Возвращаемся на исходный лист
  (princ (strcat "\n📄 Возврат на исходный лист: " original-layout))
  (setvar "ctab" original-layout)
  (princ " ✅")

  ; Включаем обратно эхо команд
  (setvar "cmdecho" 1)

  (princ "\n\n==================================================")
  (princ "\n✅ Проверка завершена!")
  (princ "\n==================================================")
  (princ "\n\n💡 Результаты проверки:")
  (princ "\n   смотрите в командной строке AutoCAD (нажмите F2)")
  (princ "\n==================================================")
  (princ)
)
